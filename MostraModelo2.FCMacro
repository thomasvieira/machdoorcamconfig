# -*- coding: utf-8 -*-

# Macro Begin: C:\Users\thoma\AppData\Roaming\FreeCAD\Macro\EscondeModelos.FCMacro +++++++++++++++++++++++++++++++++++++++++++++++++
import FreeCAD

Gui.Selection.clearSelection()
App.ActiveDocument.getObject("Job001").Label = "Usinagens Borda Direita"
App.ActiveDocument.getObject("Job").Visibility = False
App.ActiveDocument.getObject("Operations").Visibility = False
App.ActiveDocument.getObject("Stock001").Visibility = False
App.ActiveDocument.getObject("Model").Visibility = False
App.ActiveDocument.getObject("Job001").Visibility = True
App.ActiveDocument.getObject("Operations001").Visibility = True
App.ActiveDocument.getObject("Stock002").Visibility = True
App.ActiveDocument.getObject("Model001").Visibility = True
App.ActiveDocument.getObject("Job002").Visibility = False
App.ActiveDocument.getObject("Operations002").Visibility = False
App.ActiveDocument.getObject("Stock003").Visibility = False
App.ActiveDocument.getObject("Model002").Visibility = False
App.ActiveDocument.getObject("Job003").Visibility = False
App.ActiveDocument.getObject("Operations003").Visibility = False
App.ActiveDocument.getObject("Stock004").Visibility = False
App.ActiveDocument.getObject("Model003").Visibility = False
App.ActiveDocument.getObject("Job004").Visibility = False
App.ActiveDocument.getObject("Operations004").Visibility = False
App.ActiveDocument.getObject("Stock005").Visibility = False
App.ActiveDocument.getObject("Model004").Visibility = False
Gui.Selection.clearSelection()
# Macro End: C:\Users\thoma\AppData\Roaming\FreeCAD\Macro\EscondeModelos.FCMacro +++++++++++++++++++++++++++++++++++++++++++++++++
